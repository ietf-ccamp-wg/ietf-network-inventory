module ietf-inventory-types {
  namespace "urn:ietf:params:xml:ns:yang:ietf-inventory-types";
  prefix "inventory-types";

  revision 2021-09-14 {
    description
     "Initial revision.";
  }

  identity rack-type {
    description "";
  }
  
  identity component-type {
    description "";
  }
  
  identity rack {
    base component-type;
  }
  
  identity shelf {
    base component-type;
  }
  
  identity slot {
    base component-type;
  }
  
  identity sub-slot {
    base component-type;
  }
  
  identity board {
    base component-type;
  }
  
  identity physical-port {
    base component-type;
  }

}
